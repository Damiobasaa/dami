FME workspace getratings_ko.fmwt
Title: NONE to MULTI

Parameters:
- DestDataset_MSSQL_SPATIAL = ap-sqlserver9   # SQL Server Connection

Writers:
- POSTGRES_1: POSTGRES to DigitalOcean
- MSSQL_SPATIAL_1: MSSQL_SPATIAL to $(DestDataset_MSSQL_SPATIAL)

GenerateSchema: PythonCreator
    NEW_ATTRIBUTES = schema email password
    PYTHONSOURCE_NEW:
      import fmeobjects

      class FeatureCreator(object):

      	def input(self, feature):
      		for j in range(1, 5):
      				feature = fmeobjects.FMEFeature()
      				if j == 1:
      					feature.setAttribute("schema", "pace")
      					feature.setAttribute("email", "beaconapi+pace@b-21.org")
      					feature.setAttribute("password", "QF66c)1|BYl:")
      				if j == 2:
      					feature.setAttribute("schema", "weas")
      					feature.setAttribute("email", "beaconapi+weas@b-21.org")
      					feature.setAttribute("password", "pChsibVfWmZfT38")
      				if j == 3:
      					feature.setAttribute("schema", "nlis")
      					feature.setAttribute("email", "beaconapi+nlis@b-21.org")
      					feature.setAttribute("password", "nF9ztZvZKnDAtR5")
      				if j == 4:
      					feature.setAttribute("schema", "msd")
      					feature.setAttribute("email", "beaconapi+msd@b-21.org")
      					feature.setAttribute("password", "xTTGsdA6AhaYybK")


      				self.pyoutput(feature)
    PYTHONSYMBOL = FeatureCreator
    -> TruncateTables [INITIATOR]
    -> Authenticate
Authenticate: HTTPCaller
    CONNECTION_TIMEOUT_LENGTH = 60
    ERROR_ATTR = _error
    FOLLOW_REDIRECTS = Yes
    HTTP_METHOD = POST
    SAVE_FILE = Attribute
    STATUS_CODE_ATTR = _http_status_code
    TARGET_ATTR = _response_body
    TARGET_ATTR_ENCODING = auto-detect
    TARGET_URL = https://api.beaconlearning.me/v1/auth/token/obtain/
    TRANSFER_TIMEOUT_LENGTH = 90
    UPLOAD_BODY:
      {
        "email": "@Value(email)",
        "password": "@Value(password)"
      }
    UPLOAD_CONTENT_TYPE = JSON (application/json)
    UPLOAD_TYPE = Specify Upload Body
    USE_COOKIES = No
    VERIFY_SSL_CERTIFICATES = Yes
    -> ExtractToken
ExtractToken: JSONExtractor
    EXTRACT_QUERY_TABLE = accesstoken json["access"] refreshtoken json["refresh"]
    JSON_DOCUMENT = @Value(_response_body)
    READ_FROM_FILE = NO
    EVALUATED -> GetAllRatings
GetAllRatings: HTTPCaller
    CONNECTION_TIMEOUT_LENGTH = 60
    CUSTOM_HEADERS = Accept;application/json Authorization;Bearer @Value(accesstoken)
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://api.beaconlearning.me/v1/data_export/users/ratings/
    TRANSFER_TIMEOUT_LENGTH = 90
    USE_COOKIES = No
    VERIFY_SSL_CERTIFICATES = Yes
    -> ExtractStudentData
ExtractStudentData: JSONFragmenter
    EXPLODE_FORMAT = JSON
    EXTRACT_ATTR = Yes
    JSON_ATTR = _response_body
    JSON_QUERY = json["results"][*]
    NEW_ATTRIBUTES = student_external_id student_school_id
    PREF_STRING = student_
    READ_FROM_FILE = NO
    RECURSIVE = Yes
    REJECT_EMPTY_LISTS = YES
    FRAGMENTS -> ExtractTaskData
ExtractTaskData: JSONFragmenter
    EXPLODE_FORMAT = JSON
    EXTRACT_ATTR = Yes
    JSON_ATTR = _response_body
    JSON_QUERY = json["tasks"][*]
    NEW_ATTRIBUTES = task_id task_learning_experience.name task_name
    PREF_STRING = task_
    READ_FROM_FILE = NO
    RECURSIVE = Yes
    REJECT_EMPTY_LISTS = YES
    FRAGMENTS -> JoinSkillstoTask [LEFT]
    FRAGMENTS -> ExtractRatingData
ExtractRatingData: JSONFragmenter
    EXPLODE_FORMAT = JSON
    EXTRACT_ATTR = Yes
    JSON_ATTR = _response_body
    JSON_QUERY = json["evaluated_skills"][*]
    NEW_ATTRIBUTES = rating_id rating_used_for_progress rating_rating.name rating_date_added rating_date_updated rating_rating.potential_progress rating_rating.actual_progress rating_rating.performance_level_average rating_skill.code rating_level.code rating_used_for_progress
    PREF_STRING = rating_
    READ_FROM_FILE = NO
    RECURSIVE = Yes
    REJECT_EMPTY_LISTS = NO
    FRAGMENTS -> JoinSkilltoRating [LEFT]
    FRAGMENTS -> CombineSkills
CombineSkills: Aggregator
    ACCUM_ATTRS_NAME = Drop Incoming Attributes
    CONCAT_ATTRS = rating_skill.code
    GROUP_BY = task_id
    MODE = Attributes Only
    SEP = ,
    AGGREGATE -> JoinSkillstoTask [RIGHT]
JoinSkillstoTask: FeatureJoiner
    ATTR_CONFLICT_RES = Prefer Left
    GEOMETRY_HANDLING = Prefer Left
    JOIN_KEYS = task_id task_id NUM
    JOIN_MODE = Left
    JOINED -> TaskAttributes
TaskAttributes: AttributeManager
    ATTR_TABLE:
      REMOVE _response_body
      REMOVE _http_status_code
      REMOVE accesstoken
      REMOVE refreshtoken
      REMOVE json_type
      REMOVE json_index
      RENAME_SET_VALUE student_external_id > studentnumber
      RENAME_SET_VALUE task_id > taskid
      RENAME_SET_VALUE task_learning_experience.name > experiencename
      RENAME_SET_VALUE task_name > tasktitle
      SET_TO teacherstafffk = testname
      RENAME_SET_VALUE rating_skill.code > skillscodes
      REMOVE email
      REMOVE password
      REMOVE student_school_id
    USER_EXPOSED_ATTRIBUTES = _creation_instance
    -> Tester
Tester
    BOOL_OP = OR
    TEST_CLAUSE = TEST studentnumber ATTRIBUTE_HAS_A_VALUE ""
    TEST_MODE = TEST
    PASSED -> TestTable (writer MSSQL_SPATIAL_1)
TestTable (writer MSSQL_SPATIAL_1)
    attributes: studentnumber varchar_max, taskid varchar_max, experiencename varchar_max, tasktitle varchar_max, teacherstafffk varchar(200), skillscodes varchar_max, schema varchar_max
TruncateTables: SQLExecutor [off]
    ATTR_IGNORE_NULLS = Yes
    COMBINE_ATTRS = Keep Initiator Attributes if Conflict
    COMBINE_GEOM = Initiator Geometry Only
    DATASET = DigitalOcean
    FORMAT = POSTGRES
    OUTPUT_FEATURES_DISPLAY = Data Features
    POSTGRES_CREATE_FEATURE_TABLES_FROM_DATA = Yes
    POSTGRES_NAMED_CONNECTION = DigitalOcean
    POSTGRES_QUERY_FEATURE_TYPES_FOR_MERGE_FILTERS = Yes
    POSTGRES_READ_TIME_WITH_TIMEZONE = Yes
    POSTGRES_SCHEMAS_FOR_TABLE_LISTING = pace
    SQL_STATEMENT:
      truncate table @Value(schema).studentrating restart identity;
      truncate table @Value(schema).studenttask restart identity;
    INITIATOR -> GetSkillComp [INITIATOR]
GetSkillComp: SQLExecutor [off]
    ATTR_IGNORE_NULLS = Yes
    COMBINE_ATTRS = Keep Initiator Attributes if Conflict
    COMBINE_GEOM = Initiator Geometry Only
    DATASET = DigitalOcean
    EXPOSED_ATTRIBUTE_LIST = code,competencycode
    FORMAT = POSTGRES
    OUTPUT_FEATURES_DISPLAY = Data Features
    POSTGRES_CREATE_FEATURE_TABLES_FROM_DATA = Yes
    POSTGRES_NAMED_CONNECTION = DigitalOcean
    POSTGRES_QUERY_FEATURE_TYPES_FOR_MERGE_FILTERS = Yes
    POSTGRES_READ_TIME_WITH_TIMEZONE = Yes
    POSTGRES_SCHEMAS_FOR_TABLE_LISTING = pace
    SQL_STATEMENT = select code, competencycode from @Value(schema).skill
    RESULT -> JoinSkilltoRating [RIGHT]
JoinSkilltoRating: FeatureJoiner [off]
    ATTR_CONFLICT_RES = Prefer Left
    GEOMETRY_HANDLING = Prefer Left
    JOIN_KEYS = rating_skill.code code STRING schema schema STRING
    JOIN_MODE = Left
    JOINED -> RatingAttributes
RatingAttributes: AttributeManager [off]
    ATTR_TABLE:
      REMOVE _response_body
      REMOVE _http_status_code
      REMOVE accesstoken
      REMOVE refreshtoken
      REMOVE json_type
      REMOVE json_index
      RENAME_SET_VALUE student_external_id > studentnumber
      RENAME_SET_VALUE task_id > studenttaskid
      RENAME_SET_VALUE task_learning_experience.name > experiencename
      RENAME_SET_VALUE task_name > tasktitle
      REMOVE rating_id
      RENAME_SET_VALUE rating_used_for_progress > usedforer
      RENAME_SET_VALUE rating_rating.name > rating
      RENAME_SET_VALUE rating_date_added > created
      RENAME_SET_VALUE rating_date_updated > modified
      RENAME_SET_VALUE rating_rating.potential_progress > potentialprogress
      RENAME_SET_VALUE rating_rating.actual_progress > actualprogress
      RENAME_SET_VALUE rating_rating.performance_level_average > usedforPL
      RENAME_SET_VALUE rating_skill.code > skill
      RENAME_SET_VALUE rating_level.code > portfolio
      SET_TO teacherstafffk = testname
      REMOVE code
      RENAME_SET_VALUE competencycode > competency
      SET_TO usedforcalculations = true
      REMOVE student_school_id
      REMOVE email
      REMOVE password
      REMOVE _matched_records
    USER_EXPOSED_ATTRIBUTES = studentnumber,rating.value,id,rating.name,_creation_instance
    -> Tester_2
Tester_2 [off]
    BOOL_OP = AND
    TEST_CLAUSE:
      TEST studentnumber ATTRIBUTE_HAS_A_VALUE ""
      TEST competency ATTRIBUTE_HAS_A_VALUE ""
    TEST_MODE = TEST
    PASSED -> pace.studentrating (writer POSTGRES_1)
pace.studentrating (writer POSTGRES_1) [off]
    attributes: studentnumber varchar, studenttaskid varchar, experiencename varchar, tasktitle varchar, usedforer varchar, rating varchar, created varchar, modified varchar, potentialprogress varchar, actualprogress varchar, usedforpl varchar, skill varchar, portfolio varchar, teacherstafffk varchar(200), competency, usedforcalculations varchar(200), schema varchar
