FME workspace austinDownload.fmw
Title: City of Austin: Data Download
Description: This workspace allows the user to specify which data layers to download as well as the coordinate system and data format to export.
Published parameters allow the user to select:
layers to download
destination coordinate system
output data format
X and Y min/max to export
History: 22-03-2023,Kate Brillinger,Updated description

Parameters:
- THEMES = airports   # Layers to Download
- COORDSYS = LL84
- FORMAT_GENERIC = SHAPEFILE
- MINX = -100   # Minimum X
- MINY = 25   # Minimum Y
- MAXX = -90   # Maximum X
- MAXY = 35   # Maximum Y
- BBOX_COORDSYS = LL84   # Search Envelope Coordinate System

Readers:
- SHAPEFILE_1: SHAPEFILE from ""$(FME_MF_DIR)\streetcl.shp" "$(FME_MF_DIR)\railroad.shp" "$(FME_MF_DIR)\cenart.shp" "$(FME_MF_DIR)\airports.shp"" in TX83-CF

Writers:
- GENERIC_1: GENERIC to /data/fmeflow/resources/system/temp/engineresults in $(COORDSYS)

Bookmark: Source dataset feature type
Note: Your source dataset's feature type should be placed in this box and linked to the output / feature type. / You will have to add the source feature type name to the THEMES published parameter.
airports (reader SHAPEFILE_1)
    attributes: FNODE_ number(11,0), TNODE_ number(11,0), LPOLY_ number(11,0), RPOLY_ number(11,0), LENGTH number(18,5), AIRPORTS_ number(11,0), AIRPORTS_I number(11,0), LINE number(11,0), ADD_DATE char(11), NBTS number(11,0), FILLCHAR char(1), NAME char(12), STREETCL_ number(11,0), CENTERART_ number(11,0), FEA_CODE number(6,0), STREE_NAM0 char(40), STREET_TYP char(4), STREETCL_I number(11,0), STREET_NAM char(20), RAILROAD_I number(11,0), SUF_DIR char(2), RAILROAD_ number(11,0), ATS number(11,0), EXISTING number(8,0), TYPE char(20), SOURCE char(30), CENTERAR_0 number(11,0), VISIBLE char(1)
    -> Output (writer GENERIC_1)

Bookmark: Destination dataset feature type
Note: The destination feature types should / be placed in this box.
Output (writer GENERIC_1)
